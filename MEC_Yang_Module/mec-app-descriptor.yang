module mec-app-descriptor {
  namespace "http://example.com/ns/mec-app-descriptor";
  prefix mad;

  import app-network-policy { prefix anp; }
  import user-context-transfer-capability { prefix uctc; }
  import change-app-instance-state-op-config { prefix caisoc; }
  import terminate-app-instance-op-config { prefix taio; }
  import latency-descriptor { prefix ld; }
  import dns-rule-descriptor { prefix drd; }
  import feature-dependency { prefix fd; }
  import sw-image-descriptor { prefix sid; }
  import traffic-rule-descriptor { prefix trd; }
  import transport-dependency { prefix td; }
  import service-descriptor { prefix sd; }
  import app-external-cpd { prefix aecpd; }
  import service-dependency { prefix srvd; }
  import virtual-storage-descriptor { prefix vsd; }
  import virtual-compute-descriptor { prefix vcd; }
 



  description "YANG module for MEC Application Descriptors based on ETSI GS MEC 010-2 V2.2.1.";

  container app-descriptor {
    leaf appDId {
      type string;
      description "Identifier of this MEC application descriptor. This attribute shall be globally unique.";
    }
    leaf appName {
      type string;
      description "Name to identify the MEC application.";
    }
    leaf appProvider {
      type string;
      description "Provider of the application and of the AppD.";
    }
    leaf appSoftVersion {
      type string;
      description "Identifies the version of software of the MEC application.";
    }
    leaf appDVersion {
      type string;
      description "Identifies the version of the application descriptor.";
    }
    leaf mecVersion {
      type string;
      description "Identifies version(s) of MEC system compatible with the MEC application described in this version of the AppD. The value shall be formatted as comma-separated list of strings.";
    }
    leaf appInfoName {
      type string;
      description "Human readable name for the MEC application.";
    }
    leaf appDescription {
      type string;
      description "Human readable description of the MEC application.";
    }
    
    container VirtualComputeDesc {
      description "Incorporates Virtual Compute Descriptor into the MEC application descriptor.";
      list virtualCompute {
        key "id";
        uses vcd:VirtualComputeDesc;
      }
    }
    
    // Similar containers for swImageDescriptor, virtualStorageDescriptor, appExtCpd, etc., would follow
    container SwImageDescriptor {
      description "Incorporates the Software Image Descriptor into the MEC application descriptor.";
      uses sid:sw-image-descriptor-grouping;
    }

    container VirtualStorageDesc {
      description "Incorporates Virtual Storage Descriptor into the MEC application descriptor.";
      list virtualStorage {
        key "id"; 
        uses vsd:VirtualStorageDesc;
      }
    }

    list appExtCpd {
      key id;
      description "Describes an external connection point of a MEC application";
      
      leaf id {
        type string;
        description "Identifier of the external connection point";
      }
      
      uses aecpd:AppExternalCpd;
    }

    list ServiceDependency {
      key "serName";
      description "Describes service dependencies of the MEC app";
      uses srvd:ServiceDependency;
    }

    container ServiceDescriptor {
      description "Incorporates the Service Descriptor into the MEC application descriptor.";
      list service {
        key "serName";
        uses sd:ServiceDescriptor;
      }
    }

    container FeatureDependency {
      description "Incorporates the Feature Dependency into the MEC application descriptor.";
      uses fd:feature-dependency-grouping;
    }

    container TransportDependency {
      description "Incorporates the Transport Dependency into the MEC application descriptor.";
      uses td:TransportDependency;
    }

    container TrafficRuleDescriptor {
      description "Incorporates the Traffic Rule Descriptor into the MEC application descriptor.";
      uses trd:TrafficRuleDescriptor;
    }

    container DNSRuleDescriptor {
      description "Incorporates the DNS Rule Descriptor into the MEC application descriptor.";
      uses drd:dns-rule-descriptor-grouping;
    }

    container LatencyDescriptor {
      description "Incorporates the Latency Descriptor into the MEC application descriptor.";
      uses ld:latency-descriptor-grouping;
    }

    container TerminateAppInstanceOpConfig {
      description "Incorporates the Terminate Application Instance Operation Configuration into the MEC application descriptor.";
      uses taio:terminate-app-instance-op-config-grouping;
    }

    container ChangeAppInstanceStateOpConfig {
      description "Incorporates the Change Application Instance State Operation Configuration into the MEC application descriptor.";
      uses caisoc:change-app-instance-state-op-config-grouping;
    }

    container UserContextTransferCapability {
      description "Incorporates the user context transfer capability attributes into the MEC application descriptor.";
      uses uctc:user-context-transfer-capability-grouping;
    }

    container appNetworkPolicy {
      description "Container for application network policy.";
      uses anp:app-network-policy;
    }

    // For attributes with cardinality 0..N, use 'list' or 'leaf-list' as appropriate
    // Example for appServiceRequired:
    list appServiceRequired {
      key "serviceId"; // Assume there's an identifier for each service
      leaf serviceId {
        type string;
        description "Identifier for the required service.";
      }
      // Additional attributes for the service
    }
    // Similar lists for appServiceOptional, appServiceProduced, appFeatureRequired, etc., would follow
  }
}
